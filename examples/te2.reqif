# TE-2 upper-stage engine

# Specification: TE-2 upper-stage engine

## SYS-001: TE-2 meets Tern upper-stage needs
The TE-2 engine shall meet the propulsion needs of the Tern upper stage.

### PRP-001: Vacuum performance
The engine shall deliver the vacuum performance assumed in the Tern mission design.

#### PRP-010: Measured vacuum thrust
Steady-state vacuum thrust measured in the altitude cell shall be at least 20 kN.
- Provenant.Method: test
- Provenant.Condition: mean(thrust) >= 20 kN during steady_state

#### PRP-011: Predicted vacuum thrust
Predicted vacuum thrust at the nominal operating point shall be at least 20 kN.
- Provenant.Method: analysis
- Provenant.Condition: value(thrust_vac) >= 20 kN

#### PRP-044: Vacuum specific impulse
Predicted vacuum specific impulse shall be at least 315 s.
- Provenant.Method: analysis
- Provenant.Condition: value(isp_vac) >= 315 s

#### PRP-050: Burn duration
The engine shall sustain at least 90 % of nominal chamber pressure for 25 s or more.
- Provenant.Method: test
- Provenant.Condition: duration(chamber_pressure >= 108 bar) >= 25 s

### PRP-030: Chamber pressure limits
Chamber pressure shall stay within the structural and start-up limits of the thrust chamber.

#### PRP-031: Maximum chamber pressure
Chamber pressure shall never exceed 150 bar.
- Provenant.Method: test
- Provenant.Condition: max(chamber_pressure) <= 150 bar

#### PRP-033: Start-up overshoot
Chamber pressure overshoot during start-up shall not exceed 138 bar.
- Provenant.Method: test
- Provenant.Condition: max(chamber_pressure) <= 138 bar during startup

### TCS-020: Throat wall temperature
Throat wall temperature shall not exceed 900 K during steady-state operation.
- Provenant.Method: test
- Provenant.Condition: max(throat_wall_temp) <= 900 K during steady_state

### STR-012: Engine dry mass
Engine dry mass shall not exceed 95 kg.
- Provenant.Method: inspection
- Provenant.Condition: value(dry_mass) <= 95 kg

### SYS-030: Engine length in the interstage
Overall engine length shall not exceed 1.4 m.
- Provenant.Method: inspection
- Provenant.Condition: value(engine_length) <= 1.4 m

### PRP-060: Restart capability
The engine shall reach at least 90 % of nominal chamber pressure on a second ignition.
- Provenant.Method: test
- Provenant.Condition: max(chamber_pressure) >= 108 bar during second_burn
